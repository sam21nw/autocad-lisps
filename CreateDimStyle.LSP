;;Create scale relevant dim styles. Works both in model and paper space. Metres only, modify to suit your units.
(defun C:CDS ()
(princ)
(initget "V")
(setq scl (getreal "\nEnter Scale (e.g. 1:250 = 250) or select <V>iewport:  "))
(if (eq scl "V")
 (progn 
   (setq en (car (entsel "\nSelect viewport: "))
         ed (entget en)
         ph (cdr (assoc 41 ed));The ZOOM XP factor, pspace height
         mh (cdr (assoc 45 ed));model space height
        scl (/ 1000 (/ ph mh))
   )
  )
)
(setq sf (/ scl 1000))
(initget "R S A")
(setq ts (getkword "\nEnter font style <R>omans <S>implex <A>rial:  "))
(if (eq ts "R")
  (setq ts "ROMANS")
 )
 (if (eq ts "S")
  (setq ts "SIMPLEX")
 )
 (if (eq ts "A")
  (setq ts "ARIAL")
 )
(setq cmd (getvar "cmdecho"))
(setvar "cmdecho" 0)
(setq txtst (tblsearch "style" ts))
(if (eq ts "ARIAL")
 (command "-style" "DIMS" "ARIAL" "" "" "" "" "")
 (command "-style" "DIMS" ts "" "" "" "" "" "")
)
(setvar "DIMTOL" 0) 
(setvar "DIMLIM" 0)
(setvar "DIMTIH" 0)
(setvar "DIMTOH" 0)
(setvar "DIMSE1" 0)
(setvar "DIMSE2" 0)
(setvar "DIMALT" 0)
(setvar "DIMTOFL" 1)
(setvar "DIMSAH" 0)
(setvar "DIMTIX" 0)
(setvar "DIMSOXD" 0)
(setvar "DIMSD1" 0)
(setvar "DIMSD2" 0)
(setvar "DIMUPT" 0)
(setvar "DIMTOLJ" 1)
(setvar "DIMDSEP" ".")
(setvar "DIMALTD" 0)
(setvar "DIMZIN" 0)
(setvar "DIMJUST" 0)
(setvar "DIMFIT" 0)
(setvar "DIMTZIN" 0)
(setvar "DIMALTZ" 0)
(setvar "DIMALTTZ" 0)
(setvar "DIMTAD" 1)
(setvar "DIMUNIT" 2)
(setvar "DIMAUNIT" 0)
(setvar "DIMDEC" 3)
(setvar "DIMTDEC" 3)
(setvar "DIMALTU" 2)
(setvar "DIMALTTD" 0)
(setvar "DIMADEC" 0)
(setvar "DIMAZIN" 0)
(setvar "DIMATFIT" 0)
(setvar "DIMFRAC" 0)
(setvar "DIMLUNIT" 2)
(setvar "DIMTMOVE" 0)
(setvar "DIMTXSTY" "DIMS")
(setvar "DIMASZ" 4)
(setvar "DIMEXO" 2)
(setvar "DIMDLI" 0.38)
(setvar "DIMEXE" 2)
(setvar "DIMRND" 0.001)
(setvar "DIMDLE" 0)
(setvar "DIMTP" 0)
(setvar "DIMTM" 0)
(setvar "DIMTXT" 2.5)
(setvar "DIMCEN" 0.09)
(setvar "DIMTSZ" 0)
(setvar "DIMALTF" 25.4)
(setvar "DIMLFAC" (- sf (* sf 2)));;;Papespace scale
(setvar "DIMTVP" 0)
(setvar "DIMTFAC" 0.05)
(setvar "DIMGAP" 1.5)
(setvar "DIMALTRND" 0)
(setvar "DIMPOST" ".")
(setvar "DIMAPOST" ".")
(setvar "DIMBLK" ".")
(setvar "DIMBLK1" ".")
(setvar "DIMBLK2" ".")
(setvar "DIMLDRBLK" ".")
(setvar "DIMCLRD" 7)
(setvar "DIMCLRE" 7)
(if (eq ts "ARIAL")
 (setvar "DIMCLRT" 7)
 (setvar "DIMCLRT" 50)
)
(setvar "DIMLWD" -2)
(setvar "DIMLWE" -2)
(setq dimsty1 (tblsearch "dimstyle" (strcat "1to" (rtos scl 2 0) "(m)")))
(setq dimsty2 (tblsearch "dimstyle" (strcat "1to" (rtos scl 2 0) "(m)")))

  (if (= dimsty1 nil)
   (progn
    (setvar "dimscale" sf)
    (command "dimstyle" "save"  (strcat "1to" (rtos scl 2 0) "(m)"))
   )
   (progn
    (setvar "dimscale" sf)
    (command "dimstyle" "save" (strcat "1to" (rtos scl 2 0) "(m)") "y")
   )
  )
  (if (= dimsty2 nil)
   (progn
    (setvar "dimscale" 0)
    (command "dimstyle" "save" (strcat "1to" (rtos scl 2 0) "(m)" " " "MS-PS"))
   )
   (progn
    (setvar "dimscale" 0)
    (command "dimstyle" "save" (strcat "1to" (rtos scl 2 0) "(m)" " " "MS-PS") "y")
   )
  ) 
(if (/= (getvar "ctab") "Model")
 (command "dimstyle" "restore" (strcat "1to" (rtos scl 2 0) "(m)" " " "MS-PS"))
 (command "dimstyle" "restore" (strcat "1to" (rtos scl 2 0) "(m)"))
)
(setvar "cmdecho" cmd)
)
